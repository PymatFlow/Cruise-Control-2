# crs_req_func_spec

## #1: Driver Switch Request Handling (Functional)
Handle switch operations by the driver to determine the command for the cruise control system to operate upon.

### #2: Switch precedence (Functional)
If multiple switches are enabled at the same time, the cruise control system takes action in the following order:
1. Cancel
2. Cruise
3. Set
4. Resume
5. Increment
6. Decrement

### #3: Avoid repeating commands (Functional)
If the following switch operations are repeated, the system should output NoRequest the second time and after as long as the same switch is enabled:
- Cancel
- Cruise
- Set
- Resume

### #4: Long Switch recognition (Functional)
When the Increment or Decrement switches are pressed for more than 500ms, they are recognized as LongInc and LongDec respectively.

#### #5: Waiting state for Long Increment switch detection (Functional)
When the Increment switch is enabled repeatedly but it does not reach the threshold to be determined as a Long Switch operation, it outputs Inc_Middle so that a downstream function can recognize that the transition can occur.

#### #6: Waiting state for Long Decrement switch detection (Functional)
When the Decrement switch is enabled repeatedly but it does not reach the threshold to be determined as a Long Switch operation, it outputs Dec_Middle so that a downstream function can recognize that the transition can occur.

### #7: Cancel Switch Detection (Functional)
If the Cancel switch is pressed, the value of reqDrv should be set to reqMode.Cancel.

### #8: Set Switch Detection (Functional)
If the Set switch is pressed, the value of reqDrv should be set to reqMode.Set.

### #9: Enable Switch Detection (Functional)
If the Enable switch is pressed, the value of reqDrv should be set to reqMode.Cruise.

### #10: Resume Switch Detection (Functional)
If the Resume switch is pressed, the value of reqDrv should be set to reqMode.Resume.

### #11: Increment Switch Detection (Functional)
If the Increment switch is pressed, the value of reqDrv should be set as reqMode.Inc_Short, reqMode.Inc_Middle, or reqMode.Inc_Long depending on how long the switch is kept pressed.

#### #12: Increment Short Switch Detection (Functional)

#### #13: Increment Long Switch Detection (Functional)

#### #14: Intermediate state (Functional)
When the Increment switch is kept pressed and the long switch detection counter has not reached its threshold, it outputs reqMode.Inc_Middle.

### #15: Decrement Switch Detection (Functional)
If the Decrement switch is pressed, the value of reqDrv should be set as reqMode.Dec_Short, reqMode.Dec_Middle, or reqMode.Dec_Long depending on how long the switch is kept pressed.

#### #16: Decrement Short Switch Detection (Functional)

#### #17: Decrement Long Switch Detection (Functional)

#### #18: Intermediate state (Functional)
When the Decrement switch is kept pressed and the long switch detection counter has not reached its threshold, it outputs reqMode.Dec_Middle.

## #19: Cruise Control Mode (Functional)
The Cruise Control Mode module determines the operation mode of the cruise control system.
The operation mode is determined by two types of sources:
1. Output of the Driver Switch Request model
2. Environmental conditions
This module also controls the status indicator used in the instrument panel.

### #20: Disable Cruise Control system (Functional)
Conditions to disable the cruise control system.

#### #21: Key position is not ON (Functional)
The cruise control system should be disabled when the Key position is not ON.

#### #22: Gear position is not Drive (Functional)
The cruise control system should be disabled when the Gear is not in Drive position.

#### #23: Brake pressure is higher than brake_threshold (Functional)
The cruise control system should be disabled when the brake pressure is higher than brake_threshold.

### #24: Operation mode determination (Functional)
Determines the current operation mode when no external input is received.
The output operation mode is determined from the requested command and the previous operation mode.

#### #25: Precedence of mode determination (Functional)
The output operation mode has the following priorities (high to low):
- Disable
- Enable
- Resume
- Activate
- Increment
- Decrement

#### #26: Disable conditions (Functional)
Conditions that need to be active for the cruise control system to be disabled.

#### #27: Enable conditions (Functional)
Conditions that need to be active for the cruise control system to be enabled.

#### #28: Resume conditions (Functional)
Conditions that need to be active for the cruise control system to be resume operation.

#### #29: Activate conditions (Functional)
Conditions that need to be active for the cruise control system to be activated.

#### #30: Repeat previous operation mode (Functional)
Repeat the previous operation.

#### #31: Increment mode (Functional)
Increase target speed.

#### #32: Increment and hold mode (Functional)
Increase target speed and hold it.

#### #33: Decrement mode (Functional)
Decrease target speed.

#### #34: Decrement and hold mode (Functional)
Decrease target speed and hold it.

#### #35: Out of speed range detection (Functional)
If vehicle speed is less than tsp_min or higher than tsp_max, the out of speed range flag should be enabled.

#### #36: Disabling override (Functional)
If the conditions for the disabling case are detected, the disable operation mode should be overridden.

## #37: Calculate Target Speed and Throttle Value (Functional)
Calculate the target speed and the throttle value.
Input:
- Operation mode
- Vehicle speed
- Throttle value from the driver's accelerator pedal

### #38: Disabled case (Functional)
If the operation model is disabled, throttle value from the driver's accelerator pedal is used as the output throttle value.
Target Speed value is the minimum target speed.

### #39: Enabled case (Functional)
If the operation mode is enabled, target speed specifies the current vehicle speed and throttle value is set to the value from the driver's accelerator pedal.

### #40: Activated case (Functional)
If the operation mode is Activated, the output throttle value is computed as described in Target Speed Computation requirement.

#### #41: Throttle Value Computation (Functional)
Compute the throttle value from the driver's accelerator pedal

#### #42: Next Target Speed Computation (Functional)
Compute the next target speed.

### #43: Resume mode (Functional)
If the operation mode is resume, the stored target speed described in Target Speed Computation requirement is used as the current target speed and the throttle value and target speed of next step is decided as described in the Activated Case requirement.

## #44: System Interface (Container)
Cruise control system interface.

### #45: Inputs (Container)
Cruise control system inputs.

#### #46: Enable Switch (Functional)
Data-type: Boolean

#### #47: Cancel Switch (Functional)
Data-type: Boolean

#### #48: Set Switch (Functional)
Data-type: Boolean

#### #49: Resume Switch (Functional)
Data-type: Boolean

#### #50: Increment Switch (Functional)
Data-type: Boolean

#### #51: Decrement Switch (Functional)
Data-type: Boolean

#### #52: Brake pressure (Functional)

#### #53: Vehicle speed (Functional)

#### #54: Key position (Functional)

#### #55: Gear position (Functional)

#### #56: Throttle from Driver (Functional)
Throttle value from the driver's accelerator pedal.

### #57: Outputs (Container)
Outputs from the cruise control system.

#### #58: Driver Request (Functional)
Data-type: Enumeration

#### #59: Status (Functional)
Data-type: Boolean

#### #60: Operation Mode (Functional)
Cruise Control system mode of operation

#### #61: Target Speed (Functional)
Data-type: Single

#### #62: Throttle value (Functional)
Data-type: Single

### #63: Parameters (Container)
Cruise control system parameters.

#### #64: Proportional term (Functional)
Proportional term of the PI controller

#### #65: Integral term (Functional)
Integral term of the PI controller

#### #66: Threshold value for brake pressure (Functional)
Brake pressure threshold for cruise control to be disabled.

#### #67: Maximum Throttle Value (Functional)
Minimum value for the throttle should be defined as a parameter.

#### #68: Minimum Throttle Value (Functional)
Minimum value for throttle should be defined as a parameter.

#### #69: Maximum Target Speed (Functional)
Maximum value for target speed should be defined as a parameter.

#### #70: Minimum Target Speed (Functional)
Minimum value for target speed should be defined as a parameter.

## #71: Justifications
List of justified requirements

### #72: Non-functional requirement
A non-functional requirement that cannot be associated with a model element.
